"""Record whether FreeCAD executes a positional macro in a GUI process."""
from datetime import datetime, timezone
import json
from pathlib import Path
import traceback

import FreeCAD as App


OUTPUT_ROOT = Path(r"d:\github\alshield\allshield_building\outputs")
output = OUTPUT_ROOT / ("gui_bootstrap_probe_" + datetime.now().strftime("%Y%m%d_%H%M%S_%f"))
output.mkdir(parents=True, exist_ok=False)
report = {
    "status": "RUNNING",
    "started_utc": datetime.now(timezone.utc).isoformat(),
    "gui_up": bool(getattr(App, "GuiUp", False)),
}

try:
    import FreeCADGui as Gui

    document = App.newDocument("Allshield_GUI_Bootstrap_Probe")
    report["active_view_available"] = Gui.activeDocument().activeView() is not None
    App.closeDocument(document.Name)
    report["status"] = "PASS_GUI_BOOTSTRAP" if report["gui_up"] else "FAIL_GUI_NOT_INITIALIZED"
except Exception:
    report["status"] = "FAIL_GUI_BOOTSTRAP"
    report["traceback"] = traceback.format_exc()
finally:
    (output / "gui_bootstrap_probe.json").write_text(json.dumps(report, indent=2), encoding="utf-8")
    if report["gui_up"]:
        from PySide import QtCore
        QtCore.QTimer.singleShot(0, QtCore.QCoreApplication.instance().quit)
