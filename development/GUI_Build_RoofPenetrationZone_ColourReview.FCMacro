# -*- coding: utf-8 -*-
"""Create a fresh GUI review document for the DN900 roof-penetration zone."""
from pathlib import Path
from datetime import datetime
import importlib.util
import json

import FreeCAD as App
import FreeCADGui as Gui
import Part


ROOT_OVERRIDE = ''
ZONE_ID = 'Planned_Roof_Penetration_DN900_01'
ROOF_CONTEXT_IDS = (
    'SteelDeck_Envelope_A_to_Ridge1',
    'Sandwich_Ceiling_A_to_Ridge1',
)
WVB_IDS = (
    'A11_01_WVB400',
    'A11_01_WVB401_ASC',
    'A11_01_WVB401_DESC',
    'A11_01_WVB402',
    'A11_01_WVB399',
    'A11_01_WVB403',
)


def _load_module(root):
    path = root / 'development' / 'allshield_roof_penetration_zones.py'
    spec = importlib.util.spec_from_file_location('allshield_roof_penetration_zones_gui_review', str(path))
    module = importlib.util.module_from_spec(spec)
    spec.loader.exec_module(module)
    return module


def _style_context(obj, colour, transparency):
    view = getattr(obj, 'ViewObject', None)
    if view is None:
        raise AssertionError('Missing view provider for ' + obj.Name)
    for key, value in (('ShapeColor', colour), ('LineColor', colour), ('Transparency', transparency)):
        if key in view.PropertiesList:
            setattr(view, key, value)
    if 'Flat Lines' in view.listDisplayModes():
        view.DisplayMode = 'Flat Lines'
    view.Visibility = True


def _review_shape(doc, object_id, label, shape, colour, transparency=0, line_width=2.0):
    review = doc.addObject('Part::Feature', object_id)
    review.Label = label
    review.Shape = shape
    _style_context(review, colour, transparency)
    if 'LineWidth' in review.ViewObject.PropertiesList:
        review.ViewObject.LineWidth = line_width
    return review


def main():
    if not getattr(App, 'GuiUp', False):
        raise RuntimeError('Run this macro with the full FreeCAD GUI, not FreeCADCmd.')
    root = Path(ROOT_OVERRIDE) if ROOT_OVERRIDE else Path(__file__).resolve().parents[1]
    if not (root / 'development' / 'allshield_roof_penetration_zones.py').is_file():
        raise FileNotFoundError('Set ROOT_OVERRIDE to the Allshield workspace root.')
    out = root / 'outputs' / ('gui_roof_penetration_zone_' + datetime.now().strftime('%Y%m%d_%H%M%S_%f'))
    out.mkdir(parents=True, exist_ok=False)
    module = _load_module(root)
    catalog = module._load_catalog()
    doc = module.build_roof_penetration_zones(out)
    visible_ids = (ZONE_ID,) + ROOF_CONTEXT_IDS + WVB_IDS
    for object_id in visible_ids:
        if doc.getObject(object_id) is None:
            raise AssertionError('Missing review object ' + object_id)
    library = doc.getObject('Component_Library')
    if library is None:
        raise AssertionError('Missing Component_Library.')
    library.ViewObject.Visibility = False
    for prototype in library.Group:
        prototype.ViewObject.Visibility = False
    for obj in doc.Objects:
        view = getattr(obj, 'ViewObject', None)
        if view is not None:
            view.Visibility = False
    review_group = doc.addObject('App::DocumentObjectGroup', 'Review_Display_Context')
    review_group.Label = 'Review display context only | roof crest envelope and effective WVB geometry'
    roof_context = _review_shape(
        doc,
        'Review_Roof_Crest_Envelope_A_to_Ridge1',
        'Review context | C4a roof crest envelope A to ridge 1',
        Part.getShape(doc.getObject(ROOF_CONTEXT_IDS[0])).copy(),
        (0.60, 0.66, 0.70),
        transparency=85,
        line_width=3.0,
    )
    wvb_context = _review_shape(
        doc,
        'Review_Axis01_WVB_Effective_Geometry',
        'Review context | effective A11 axis-1 WVB geometry',
        Part.makeCompound([Part.getShape(doc.getObject(object_id)).copy() for object_id in WVB_IDS]),
        (0.82, 0.20, 0.05),
        line_width=3.0,
    )
    review_group.addObject(roof_context)
    review_group.addObject(wvb_context)
    marker = doc.getObject(ZONE_ID)
    _style_context(marker, tuple(float(value) for value in catalog['change_visualisation']['rgb']), 0)
    if 'LineWidth' in marker.ViewObject.PropertiesList:
        marker.ViewObject.LineWidth = 4.0
    doc.recompute()
    active_view = Gui.activeDocument().activeView()
    active_view.viewTop()
    active_view.fitAll()
    Gui.updateGui()
    context_screenshot = out / 'Roof_Penetration_Zone_GUI_context_top.png'
    active_view.saveImage(str(context_screenshot), 1800, 1200, 'Current')
    review_group.ViewObject.Visibility = False
    active_view.viewTop()
    active_view.fitAll()
    Gui.updateGui()
    detail_screenshot = out / 'Roof_Penetration_Zone_GUI_detail_top.png'
    active_view.saveImage(str(detail_screenshot), 1800, 1200, 'Current')
    review_group.ViewObject.Visibility = True
    active_view.viewAxonometric()
    active_view.fitAll()
    Gui.updateGui()
    target = out / 'Roof_Penetration_Zone_GUI_review.FCStd'
    doc.saveAs(str(target))
    report = {
        'status': 'GUI_ROOF_PENETRATION_ZONE_REVIEW_READY',
        'fcstd': str(target),
        'context_screenshot': str(context_screenshot),
        'detail_screenshot': str(detail_screenshot),
        'visible_context_ids': list(visible_ids),
        'review_context_geometry': [roof_context.Name, wvb_context.Name],
        'physical_roof_cutout_created': False,
        'panel_containment_verified': False,
        'known_modelled_wvb_clearance_checked': True,
        'manual_visual_review_required': True,
        'as_built_verified': False,
        'fabrication_model': False,
    }
    (out / 'gui_roof_penetration_zone_review.json').write_text(json.dumps(report, indent=2), encoding='utf-8')
    App.Console.PrintMessage('Roof penetration zone GUI review: ' + str(out) + '\n')


main()
